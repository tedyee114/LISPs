(defun C:fooj()
  ;(setq LAYLIST)
  ;(Setq NUM)
  ;(setq LAYCUR (LAYLIST NUM))
  ;(command "_LAYFRZ" "*" "")
  ;(command "_LAYTHW" "B-OVERHANG" "")
 (setq expert (getvar "expert"))
 (setvar "expert" 1)
 (command "._layer" "_off" "*" "_on" "B-OVERHANG" "")
 (setvar "expert" expert)
 (princ)
)
