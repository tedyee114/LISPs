(defun C:fon ()
  (setq ERRORLIST (list "Hi"))
  (setq LAYCUR "R-ROAD-ASPH") (cleaner)
  (setq LAYCUR "B-OVERHANG")  (cleaner)
  (print ERRORLIST)
  ;; (print "Errors on:      ")
  ;; (while ERRORLIST
  ;;   (print (car ERRORLIST))
  ;;   (setq ERRORLIST (cdr ERRORLIST)))
)

(defun cleaner ()
  (if (not (tblsearch "layer" "GEOS-R-TEMP")) 
    (command "_layer" "m" "GEOS-R-TEMP" "")
  )
  (command "_layer" "set" LAYCUR "")
  (command "_layer" "_off" "*" "N" "")
  (command "_layer" "_on" LAYCUR "_on" "GEOS-R-TEMP" "")
  (command "_mapclean" "GEOS-R-TEMP")
  (setq num (ssget "_A" '((8 . "GEOS-R-TEMP"))))

  (if (/= num 0)
    (setq ERRORLIST (append ERRORLIST (list LAYCUR)))
  )
  (command "_laydel" "n" "GEOS-R-TEMP" "" "Y" "")
  (command "_layer" "_on" "*" "")
 )
