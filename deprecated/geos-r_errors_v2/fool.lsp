(defun C:fool()
  ;(setq LAYLIST)
  ;(Setq NUM)
  ;(setq LAYCUR (LAYLIST NUM))
  ;(command "_LAYFRZ" "*" "")
  ;(command "_LAYTHW" "B-OVERHANG" "")
  (setq LAYCUR "B-OVERHANG")
 (setq expert (getvar "expert"))
 (setvar "expert" 1)
 (command "._layer" "_off" "*" "_on" LAYCUR "")
 (setvar "expert" expert)
 (princ)
 (command "_mapclean" "lay0dups")
)
